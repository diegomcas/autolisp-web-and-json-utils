;*************************************************************************************************
;* INICIO api_call.lsp
;*************************************************************************************************

;;----------------------------------------------------------------------------------
;;get_from_web function.
;;Conect to a url as a API service and get the response
;;Params:
;;       -str_url (string): Url of API service
;;       -lst_headers (string): list of lists of the form (("HeaderParam" "ValueOfHeaderParam"))
;;       -str_method (string): HTTP methods 'GET', 'POST', 'PUT', etc
;;       -str_post_data: Data to send to the server (json text, for example)
;;
;;For example:
;;In an DRF tokenized authentication -> GET things from server:
;;  get_from_web("http://urlofservice/" "GET" nil (("Authorization" "Token YourUserToken")))
;;
;;In an DRF tokenized authentication -> POST json to the server:
;;  get_from_web(
;;      "http://urlofservice/"
;;      "POST"
;;      "{tag: value, tag1: value1}"
;;      (("Authorization" "Token YourUserToken") ("Content-Type" "application/json")))
;;
;;RETURN: A list of dotted lists:
;;        (
;;          ('Status . "Status Code")
;;          ('StatusText . "Status Text")
;;          ('ResponseText . "response_text")
;;          ('ResponseAnsiText . "response_text")
;;          ('ErrorValue . "err_obj")
;;        )
;;If 'ErrorValue == nil -> The server response some valid thing
;;Else 'ErrorValue contain the error
;;
;; Original Code posted by user: BazzaCAD, 2010/03/29, from site:
;; http://opendcl.com/forum/index.php?topic=1244.0
;; Obtained From https://forums.autodesk.com/t5/visual-lisp-autolisp-and-general/make-an-api-call-with-autolisp-visuallisp/td-p/9083202
;; Posted by CodeDing, 2019/12/10
;;
;; Modified by (me ;-) ) diegomcas@gmail.com 2020/03/08
;;----------------------------------------------------------------------------------
(defun dmc:web:get_from_web (str_url str_method str_post_data lst_headers
                     / web_obj server_response err_obj response_body status content_type)
  
  (if (not str_method)
    (setq str_method "GET")
  )

  ;; Create a new reference to the WinHttp object
  (setq web_obj
    (vlax-invoke-method
      (vlax-get-acad-object)
      'GetInterfaceObject
      "WinHttp.WinHttpRequest.5.1"
    )
  )

  ;; Fetch web page
  (vlax-invoke-method web_obj 'Open str_method str_url :vlax-false)

  ;; Add/replace a request header.
  (foreach header_tup lst_headers
    (vlax-invoke-method web_obj 'SetRequestHeader (car header_tup) (cadr header_tup))
  )
  
  ;; Sending request
  (if str_post_data
    (setq err_obj (vl-catch-all-apply 'vlax-invoke-method (list web_obj 'Send str_post_data)))
    (setq err_obj (vl-catch-all-apply 'vlax-invoke-method (list web_obj 'Send)))
  )

  (if (null (vl-catch-all-error-p err_obj))
    (progn
      (setq status (vlax-get-property web_obj 'Status))
      
      ; (princ "status: ")(princ status)(princ "\n")

      (if (and (>= status 200) (< status 300)) ;; Applying corrections to characters utf codes
        (setq response_body
          (vl-list->string
            (dmc:web:list_latin_utf_to_ascii
              (vlax-safearray->list
                (vlax-variant-value
                  (vlax-get-property web_obj 'ResponseBody)
                )
              )
            )
          )
        )
      )
      
      ; (princ "response_body: ")(princ response_body)(princ "\n")

      (setq content_type (vl-catch-all-apply 'vlax-invoke-method (list web_obj 'GetResponseHeader "Content-Type")))
      (if (not (null (vl-catch-all-error-p content_type)))
        (setq content_type "Undefinied")
      )
      
      (setq server_response
        (list
          (cons 'Status status)
          (cons 'StatusText (vlax-get-property web_obj 'StatusText))
          (cons 'ResponseText (vlax-get-property web_obj 'ResponseText))
          (cons 'ResponseAnsiText response_body)
          (cons 'Content-Type content_type)
          (cons 'ErrorValue nil)
        )
      )
    )
    (progn
      (setq server_response
        (list
          (cons 'Status nil)
          (cons 'StatusText nil)
          (cons 'ResponseText nil)
          (cons 'ResponseAnsiText nil)
          (cons 'Content-Type nil)
          (cons 'ErrorValue (vl-catch-all-error-message err_obj))
        )
      )
    )
  )

  (if web_obj (vlax-release-object web_obj))
  
  server_response 
)

;;----------------------------------------------------------------------------------
;;list_latin_utf_to_ascii function.
;;From a list of characters integer values return a new list with the utfs codes translates
;;Params:
;;       -lst_code: The list with the original codes
;;
;;RETURN: A list with the ansi latin codes.
;;
;;Original Code by: diegomcas, 2020/03/25
;;----------------------------------------------------------------------------------
(defun dmc:web:list_latin_utf_to_ascii (lst_code / lst_translate cnt code_ext new_code)
  ; lst_code = Lista con los codigos del string
  (setq cnt 0)
  (while (< cnt (length lst_code))
    (setq code (nth cnt lst_code))
    (if (> code 127) ;Wait a new integer code
      (progn
        (setq cnt (1+ cnt))
        (setq code_ext (nth cnt lst_code))
        (if (eq 194 code) ;Without displacement, otherwise displacement +64
          (setq new_code code_ext)
          (setq new_code (+ code_ext 64))
        )
      )
      (progn
        (setq new_code code)
      )
    )
    (setq lst_translate (append lst_translate (list new_code)))
    (setq cnt (1+ cnt))
  )
  lst_translate
)

;;----------------------------------------------------------------------------------
;;get_DRF_token function.
;;Only this :-) Get the DRF (Django Rest Full) Token. Use the (get_from_web) function
;;Params:
;;       -url_to_api-token-auth: The url to get the token
;;       -username: The Username
;;       -password: The Password
;;
;;RETURN: A list with the complete response of the function (get_from_web) (car element)
;;        and the TOKEN (cadr element)
;;
;;Original Code by: diegomcas, 2020/03/25
;;----------------------------------------------------------------------------------
(defun dmc:web:get_DRF_token (url_to_api-token-auth username password / response_list token)
  (setq response_list
    (dmc:web:get_from_web url_to_api-token-auth
      "POST"
      (dmc:json:list_to_json
        (list
          (list "username" username)
          (list "password" password)
        )
      )
      (list (list "Content-Type" "application/json"))
    )
  )
  
  (if (null (cdr (assoc 'ErrorValue response_list)))
    (progn
      (if (equal (cdr (assoc 'Status response_list)) 200)
        (progn
          (setq token (cadr (car (dmc:json:json_to_list (cdr (assoc 'ResponseText response_list))))))
         )
      )
    )
  )

  (list response_list token)
)

;;----------------------------------------------------------------------------------
;;send_file function.
;;Use binary_file function and get_from_web function to send files to API
;;Params:
;;       -url_to_api: The url to send the file
;;       -file_name: The local file name to send
;;
;;RETURN: A list with the complete response of the function (get_from_web)
;;
;;Original Code by: diegomcas, 2021/02/05
;;----------------------------------------------------------------------------------
(defun dmc:web:send_file (url_to_api file_name / response_upload binary_file)
  (if (findfile file_name)
		(progn
      (setq binary_file (dmc:web:read_binary_stream file_name 0))
      (setq response_upload (dmc:web:get_from_web url_to_api "PUT" binary_file
        ((list
          (list "Authorization" (strcat "Token " GLOBAL_TOKEN))
          (list "Content-Type" "application/octet-stream")
        ))
      ))
    )
    (progn
    )
  )
)

(defun dmc:web:read_binary_stream (file_name len / ADOStream result )
  (setq result
    (vl-catch-all-apply
      (function
        (lambda ( / size )
          (setq ADOStream (vlax-create-object "ADODB.Stream"))
          (vlax-invoke ADOStream 'Open)
          (vlax-put-property ADOStream 'type 1)
          (vlax-invoke-method ADOStream 'loadfromfile filename)
          (vlax-put-property ADOStream 'position 0)
          (setq size (vlax-get ADOStream 'size))
          (vlax-invoke-method ADOStream 'read (if (and (numberp len) (< 0 len size)) (fix len) -1))
        )
      )
    )
  )
  (if ADOStream (vlax-release-object ADOStream))

  (if (not (vl-catch-all-error-p result))
    result
  )
)

;*************************************************************************************************
;* FIN api_call.lsp
;*************************************************************************************************
